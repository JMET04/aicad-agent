; Real-host integration test for AutoCAD Core Console and full AutoCAD.
; All paths are supplied through AICAD_TEST_ROOT to keep this source ASCII-only.

(vl-load-com)

(defun aicad-test:emit (stream text)
  (write-line text stream)
  (princ (strcat "\n" text))
)

(defun aicad-test:close-point-p (a x y tolerance)
  (and (<= (abs (- (car a) x)) tolerance)
       (<= (abs (- (cadr a) y)) tolerance))
)

(defun aicad-test:selection-count ()
  (setq aicad-test:ss (ssget "_X" (list '(0 . "LINE") (cons 8 aicad:*layer*))))
  (if aicad-test:ss (sslength aicad-test:ss) 0)
)

(defun aicad-test:check-entities (stream / expected ss index data xdata payload id step item start end seen ok)
  (setq expected
    (list
      (list "L001" 0.0 0.0 120.0 0.0 1)
      (list "L002" 120.0 0.0 120.0 80.0 2)
      (list "L003" 120.0 80.0 0.0 80.0 3)
      (list "L004" 0.0 80.0 0.0 0.0 4))
    ss (ssget "_X" (list '(0 . "LINE") (cons 8 aicad:*layer*)))
    index 0 seen '() ok T)
  (if (not ss)
    (progn (aicad-test:emit stream "FAIL:NO_AICAD_LINES") (setq ok nil))
    (progn
      (if (/= (sslength ss) 4)
        (progn (aicad-test:emit stream (strcat "FAIL:ENTITY_COUNT=" (itoa (sslength ss)))) (setq ok nil)))
      (repeat (sslength ss)
        (setq data (entget (ssname ss index) (list aicad:*regapp*))
              xdata (assoc -3 data)
              payload (if xdata (cadr xdata) nil)
              id (if payload (cdr (assoc 1000 (cdr payload))) nil)
              step (if payload (cdr (assoc 1070 (cdr payload))) nil)
              start (cdr (assoc 10 data))
              end (cdr (assoc 11 data))
              item (if id (assoc id expected) nil))
        (cond
          ((not xdata) (aicad-test:emit stream "FAIL:MISSING_XDATA") (setq ok nil))
          ((not item) (aicad-test:emit stream "FAIL:UNKNOWN_ID") (setq ok nil))
          ((member id seen) (aicad-test:emit stream (strcat "FAIL:DUPLICATE_ID=" id)) (setq ok nil))
          ((/= step (nth 5 item)) (aicad-test:emit stream (strcat "FAIL:STEP=" id)) (setq ok nil))
          ((not (aicad-test:close-point-p start (nth 1 item) (nth 2 item) 0.000001))
            (aicad-test:emit stream (strcat "FAIL:START=" id)) (setq ok nil))
          ((not (aicad-test:close-point-p end (nth 3 item) (nth 4 item) 0.000001))
            (aicad-test:emit stream (strcat "FAIL:END=" id)) (setq ok nil))
          (T (aicad-test:emit stream (strcat "PASS:ENTITY=" id))))
        (if id (setq seen (cons id seen)))
        (setq index (1+ index))
      )
      (if (/= (length seen) 4)
        (progn (aicad-test:emit stream "FAIL:ID_COUNT") (setq ok nil)))
    )
  )
  ok
)

(defun aicad-integration-run (/ root plugin plan report output stream draw-result ok)
  (setq root (vl-string-translate "\\" "/" (getenv "AICAD_TEST_ROOT"))
        plugin (strcat root "/AiCadConstraint.lsp")
        plan (strcat root "/rectangle.aicad")
        report (strcat root "/integration-report.txt")
        output (strcat root "/result.dwg")
        stream (open report "w")
        ok T)
  (setvar "FILEDIA" 0)
  (aicad-test:emit stream "AICAD_INTEGRATION_BEGIN")
  (aicad-test:emit stream (strcat "HOST_ACADVER=" (getvar "ACADVER")))
  (aicad-test:emit stream (strcat "HOST_LISPSYS=" (itoa (getvar "LISPSYS"))))
  (command "_.ERASE" "_ALL" "")
  (if (not (load plugin nil))
    (progn (aicad-test:emit stream "FAIL:PLUGIN_LOAD") (setq ok nil))
    (aicad-test:emit stream "PASS:PLUGIN_LOAD"))
  (if ok
    (progn
      (setq draw-result (aicad:draw-file plan))
      (if (not (car draw-result))
        (progn (aicad-test:emit stream (strcat "FAIL:DRAW=" (cadr draw-result))) (setq ok nil))
        (progn
          (aicad-test:emit stream (strcat "PASS:DRAW_COUNT=" (itoa (cadr draw-result))))
          (if (not (aicad-test:check-entities stream)) (setq ok nil))
          (aicad-test:emit stream "SKIP:UNDO_REQUIRES_GUI_OUTSIDE_SCRIPT_GROUP")
          (command "_.SAVEAS" "2018" output)
          (if (findfile output)
            (aicad-test:emit stream "PASS:SAVE_DWG")
            (progn (aicad-test:emit stream "FAIL:SAVE_DWG") (setq ok nil)))
        )
      )
    )
  )
  (aicad-test:emit stream (if ok "AICAD_INTEGRATION_PASS" "AICAD_INTEGRATION_FAIL"))
  (close stream)
  ok
)

(defun aicad-persistence-run (/ root plugin report stream ok)
  (setq root (vl-string-translate "\\" "/" (getenv "AICAD_TEST_ROOT"))
        plugin (strcat root "/AiCadConstraint.lsp")
        report (strcat root "/persistence-report.txt")
        stream (open report "w")
        ok T)
  (aicad-test:emit stream "AICAD_PERSISTENCE_BEGIN")
  (if (not (load plugin nil))
    (progn (aicad-test:emit stream "FAIL:PLUGIN_LOAD") (setq ok nil))
    (aicad-test:emit stream "PASS:PLUGIN_LOAD"))
  (if (and ok (not (aicad-test:check-entities stream))) (setq ok nil))
  (aicad-test:emit stream (if ok "AICAD_PERSISTENCE_PASS" "AICAD_PERSISTENCE_FAIL"))
  (close stream)
  ok
)
