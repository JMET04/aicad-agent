; Protocol 3 layer, Unicode TEXT, style, XData, and save/reopen verification.
; This source remains ASCII-only: the expected Chinese identifier uses AutoCAD \U+ escaping.
(vl-load-com)

(defun aicad-v3:emit (stream text)
  (write-line text stream)
  (princ (strcat "\n" text))
)

(defun aicad-v3:one (kind layer / ss)
  (setq ss (ssget "_X" (list (cons 0 kind) (cons 8 layer))))
  (if (and ss (= (sslength ss) 1)) (ssname ss 0) nil)
)

(defun aicad-v3:point-p (point x y)
  (and point (equal (car point) x 0.000001) (equal (cadr point) y 0.000001))
)

(defun aicad-v3:xdata-p (entity expected-id expected-kind / data xdata payload strings step)
  (setq data (entget entity (list aicad:*regapp*))
        xdata (assoc -3 data)
        payload (if xdata (cdr (cadr xdata)) nil)
        strings (if payload (vl-remove-if-not '(lambda (item) (= (car item) 1000)) payload) nil)
        step (if payload (cdr (assoc 1070 payload)) nil))
  (and (= (length strings) 2)
       (= (cdr (nth 0 strings)) expected-id)
       (= (cdr (nth 1 strings)) expected-kind)
       step (> step 0))
)

(defun aicad-v3:layer-p (layer expected-linetype expected-lineweight / data)
  (setq data (entget (tblobjname "LAYER" layer)))
  (and data
       (= (strcase (cdr (assoc 6 data))) (strcase expected-linetype))
       (= (cdr (assoc 370 data)) expected-lineweight))
)

(defun aicad-v3:check (stream / line circle text line-data circle-data text-data ok)
  (setq line (aicad-v3:one "LINE" "GRID")
        circle (aicad-v3:one "CIRCLE" "GRID_BUBBLE")
        text (aicad-v3:one "TEXT" "GRID_TEXT")
        ok T)
  (if (not (and line circle text))
    (progn (aicad-v3:emit stream "FAIL:SEMANTIC_ENTITY_COUNTS") (setq ok nil))
    (progn
      (setq line-data (entget line)
            circle-data (entget circle)
            text-data (entget text))
      (if (not (and (aicad-v3:point-p (cdr (assoc 10 line-data)) 0.0 0.0)
                    (aicad-v3:point-p (cdr (assoc 11 line-data)) 0.0 1000.0)))
        (progn (aicad-v3:emit stream "FAIL:GRID_GEOMETRY") (setq ok nil)))
      (if (not (and (aicad-v3:point-p (cdr (assoc 10 circle-data)) 0.0 1200.0)
                    (equal (cdr (assoc 40 circle-data)) 100.0 0.000001)))
        (progn (aicad-v3:emit stream "FAIL:BUBBLE_GEOMETRY") (setq ok nil)))
      (aicad-v3:emit stream (strcat "EVIDENCE:TEXT_LENGTH=" (itoa (strlen (cdr (assoc 1 text-data))))))
      (aicad-v3:emit stream (strcat "EVIDENCE:TEXT_FIRST_CODE=" (itoa (ascii (substr (cdr (assoc 1 text-data)) 1 1)))))
      (aicad-v3:emit stream (strcat "EVIDENCE:TEXT_ALIGN=" (itoa (cdr (assoc 72 text-data))) "," (itoa (cdr (assoc 73 text-data)))))
      (aicad-v3:emit stream (strcat "EVIDENCE:GRID_STYLE=" (cdr (assoc 6 (entget (tblobjname "LAYER" "GRID")))) "," (itoa (cdr (assoc 370 (entget (tblobjname "LAYER" "GRID")))))))
      (if (not (and (= (cdr (assoc 1 text-data)) "\U+8F741")
                    (aicad-v3:point-p (cdr (assoc 11 text-data)) 0.0 1200.0)
                    (equal (cdr (assoc 40 text-data)) 80.0 0.000001)
                    (= (cdr (assoc 72 text-data)) 1)
                    (= (cdr (assoc 73 text-data)) 2)))
        (progn (aicad-v3:emit stream "FAIL:TEXT_VALUE_OR_PLACEMENT") (setq ok nil)))
      (if (not (and (aicad-v3:xdata-p line "AX1" "LINE")
                    (aicad-v3:xdata-p circle "AX1B" "CIRCLE")
                    (aicad-v3:xdata-p text "AX1T" "TEXT")))
        (progn (aicad-v3:emit stream "FAIL:XDATA") (setq ok nil)))
      (if (not (and (aicad-v3:layer-p "GRID" "CENTER2" 13)
                    (aicad-v3:layer-p "GRID_BUBBLE" "Continuous" 18)
                    (aicad-v3:layer-p "GRID_TEXT" "Continuous" 18)))
        (progn (aicad-v3:emit stream "FAIL:LAYER_STYLE") (setq ok nil)))
      (if ok (aicad-v3:emit stream "PASS:PROTOCOL3_TEXT_LAYER_XDATA"))))
  ok
)

(defun aicad-v3:run (/ root plugin plan report output stream result ok)
  (setq root (vl-string-translate "\\" "/" (getenv "AICAD_TEST_ROOT"))
        plugin (strcat root "/AiCadConstraint.lsp")
        plan (strcat root "/protocol3-text-layer.aicad")
        report (strcat root "/v3-report.txt")
        output (strcat root "/result-v3.dwg")
        stream (open report "w") ok T)
  (setvar "FILEDIA" 0)
  (command "_.ERASE" "_ALL" "")
  (aicad-v3:emit stream "AICAD_V3_BEGIN")
  (aicad-v3:emit stream (strcat "HOST_ACADVER=" (getvar "ACADVER")))
  (aicad-v3:emit stream (strcat "HOST_LISPSYS=" (itoa (getvar "LISPSYS"))))
  (if (not (load plugin nil))
    (progn (aicad-v3:emit stream "FAIL:PLUGIN_LOAD") (setq ok nil)))
  (if ok
    (progn
      (setq result (aicad:draw-file plan))
      (if (not (and (car result) (= (cadr result) 3)))
        (progn (aicad-v3:emit stream "FAIL:DRAW_RESULT") (setq ok nil))
        (if (not (aicad-v3:check stream)) (setq ok nil)))))
  (if ok
    (progn
      (command "_.SAVEAS" "2018" output)
      (if (findfile output)
        (aicad-v3:emit stream "PASS:SAVE_DWG")
        (progn (aicad-v3:emit stream "FAIL:SAVE_DWG") (setq ok nil)))))
  (aicad-v3:emit stream (if ok "AICAD_V3_PASS" "AICAD_V3_FAIL"))
  (close stream)
  ok
)

(defun aicad-v3:persistence-run (/ root plugin report stream ok)
  (setq root (vl-string-translate "\\" "/" (getenv "AICAD_TEST_ROOT"))
        plugin (strcat root "/AiCadConstraint.lsp")
        report (strcat root "/v3-persistence-report.txt")
        stream (open report "w") ok T)
  (aicad-v3:emit stream "AICAD_V3_PERSISTENCE_BEGIN")
  (if (not (load plugin nil))
    (progn (aicad-v3:emit stream "FAIL:PLUGIN_LOAD") (setq ok nil)))
  (if (and ok (not (aicad-v3:check stream))) (setq ok nil))
  (aicad-v3:emit stream (if ok "AICAD_V3_PERSISTENCE_PASS" "AICAD_V3_PERSISTENCE_FAIL"))
  (close stream)
  ok
)
