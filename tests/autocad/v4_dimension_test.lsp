; Protocol 4 native DIMENSION, DIMSTYLE, XData, and save/reopen verification.
; ASCII-only host fixture.
(vl-load-com)

(defun aicad-v4:emit (stream text)
  (write-line text stream)
  (princ (strcat "\n" text))
)

(defun aicad-v4:xdata-values (entity / data xdata payload)
  (setq data (entget entity (list aicad:*regapp*))
        xdata (assoc -3 data)
        payload (if xdata (cdr (cadr xdata)) nil))
  (if payload (vl-remove-if-not '(lambda (item) (= (car item) 1000)) payload) nil)
)

(defun aicad-v4:check-dimension (entity expected stream / values data id purpose kind measurement subtype actual-subtype class-name ok)
  ; Core Console has no Application COM object. Validate persisted native DXF
  ; properties directly from AutoCAD's entity database instead.
  (setq values (aicad-v4:xdata-values entity)
        data (entget entity (list aicad:*regapp*))
        id (if values (cdr (nth 0 values)) "")
        purpose (nth 1 expected)
        kind (nth 2 expected)
        measurement (nth 3 expected)
        subtype (nth 4 expected)
        actual-subtype (logand 7 (cdr (assoc 70 data)))
        class-name (if (= actual-subtype 1) "AcDbAlignedDimension" "AcDbRotatedDimension")
        ok T)
  (if (not (= id (car expected))) (setq ok nil))
  (if (not (and (= (length values) 5)
                (= (cdr (nth 1 values)) "DIMENSION")
                (= (cdr (nth 2 values)) (strcat "DIM_PURPOSE:" purpose))
                (= (cdr (nth 3 values)) "DIM_STYLE:AICAD_ARCH")
                (= (cdr (nth 4 values)) (strcat "DIM_KIND:" kind))))
    (setq ok nil))
  (if (not (= (strcase (cdr (assoc 8 data))) "DIMENSION")) (setq ok nil))
  (if (not (= (cdr (assoc 3 data)) "AICAD_ARCH")) (setq ok nil))
  (if (not (equal (cdr (assoc 42 data)) measurement 0.000001)) (setq ok nil))
  (if (not (= actual-subtype subtype)) (setq ok nil))
  (aicad-v4:emit stream (strcat "EVIDENCE:" id "=" (rtos (cdr (assoc 42 data)) 2 6) "," class-name))
  ok
)

(defun aicad-v4:check (stream / selection expected index entity values id row seen ok style-data)
  (setq selection (ssget "_X" '((0 . "DIMENSION") (8 . "DIMENSION")))
        expected '(
          ("D_OVERALL_X" "overall" "horizontal" 1000.0 0)
          ("D_GRID_X" "grid" "horizontal" 1000.0 0)
          ("D_PARTITION_Y" "partition" "vertical" 800.0 0)
          ("D_OPENING_X" "opening" "horizontal" 1000.0 0)
          ("D_ALIGNED" "general" "aligned" 500.0 1)
        )
        seen '() ok T)
  (if (not (and selection (= (sslength selection) 5)))
    (progn (aicad-v4:emit stream "FAIL:DIMENSION_COUNT") (setq ok nil))
    (progn
      (setq index 0)
      (while (< index (sslength selection))
        (setq entity (ssname selection index)
              values (aicad-v4:xdata-values entity)
              id (if values (cdr (nth 0 values)) "")
              row (assoc id expected))
        (if (or (not row) (not (aicad-v4:check-dimension entity row stream)))
          (progn (aicad-v4:emit stream (strcat "FAIL:DIMENSION_ENTITY:" id)) (setq ok nil)))
        (setq seen (cons id seen) index (1+ index)))
      (foreach row expected
        (if (not (member (car row) seen))
          (progn (aicad-v4:emit stream (strcat "FAIL:MISSING_ID:" (car row))) (setq ok nil))))))
  (setq style-data (if (tblsearch "DIMSTYLE" "AICAD_ARCH") (entget (tblobjname "DIMSTYLE" "AICAD_ARCH")) nil))
  (if (not (and style-data
                (equal (cdr (assoc 140 style-data)) 280.0 0.000001)
                (equal (cdr (assoc 41 style-data)) 180.0 0.000001)
                (equal (cdr (assoc 142 style-data)) 150.0 0.000001)))
    (progn (aicad-v4:emit stream "FAIL:DIMSTYLE") (setq ok nil)))
  (if ok (aicad-v4:emit stream "PASS:PROTOCOL4_NATIVE_DIMENSION_XDATA"))
  ok
)

(defun aicad-v4:run (/ root plugin plan report output stream result ok)
  (setq root (vl-string-translate "\\" "/" (getenv "AICAD_TEST_ROOT"))
        plugin (strcat root "/AiCadConstraint.lsp")
        plan (strcat root "/native-dimensions.aicad")
        report (strcat root "/v4-report.txt")
        output (strcat root "/result-v4.dwg")
        stream (open report "w") ok T)
  (setvar "FILEDIA" 0)
  (command "_.ERASE" "_ALL" "")
  (aicad-v4:emit stream "AICAD_V4_BEGIN")
  (aicad-v4:emit stream (strcat "HOST_ACADVER=" (getvar "ACADVER")))
  (if (not (load plugin nil))
    (progn (aicad-v4:emit stream "FAIL:PLUGIN_LOAD") (setq ok nil)))
  (if ok
    (progn
      (setq result (aicad:draw-file plan))
      (if (not (and (car result) (= (cadr result) 10)))
        (progn
          (aicad-v4:emit stream (strcat "FAIL:DRAW_RESULT:" (if (cadr result) (vl-princ-to-string (cadr result)) "NO_DETAIL")))
          (setq ok nil))
        (if (not (aicad-v4:check stream)) (setq ok nil)))))
  (if ok
    (progn
      (command "_.SAVEAS" "2018" output)
      (if (findfile output)
        (aicad-v4:emit stream "PASS:SAVE_DWG")
        (progn (aicad-v4:emit stream "FAIL:SAVE_DWG") (setq ok nil)))))
  (aicad-v4:emit stream (if ok "AICAD_V4_PASS" "AICAD_V4_FAIL"))
  (close stream)
  ok
)

(defun aicad-v4:persistence-run (/ root plugin report stream ok)
  (setq root (vl-string-translate "\\" "/" (getenv "AICAD_TEST_ROOT"))
        plugin (strcat root "/AiCadConstraint.lsp")
        report (strcat root "/v4-persistence-report.txt")
        stream (open report "w") ok T)
  (aicad-v4:emit stream "AICAD_V4_PERSISTENCE_BEGIN")
  (if (not (load plugin nil))
    (progn (aicad-v4:emit stream "FAIL:PLUGIN_LOAD") (setq ok nil)))
  (if (and ok (not (aicad-v4:check stream))) (setq ok nil))
  (aicad-v4:emit stream (if ok "AICAD_V4_PERSISTENCE_PASS" "AICAD_V4_PERSISTENCE_FAIL"))
  (close stream)
  ok
)
